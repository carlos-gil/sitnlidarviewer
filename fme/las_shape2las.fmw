FME workspace las_shape2las.fmw

Parameters:
- SourceDataset_CSV = C:\Projets\LiDARViewer\data\1164212.asc   # Source Comma Separated Value (CSV) File(s)
- DestDataset_JSON = C:\OSGeo4W\apache\htdocs\lidaviewer\data\demo.json   # Destination JSON (JavaScriptObjectNotation) File
- SourceDataset_LAS = C:\Projets\LiDARViewer\data\1164212.las   # Source ASPRS LAS File(s)

Readers:
- CSV_1: CSV from $(SourceDataset_CSV)
- LAS_1: LAS from $(SourceDataset_LAS)

Writers:
- JSON_1: JSON to $(DestDataset_JSON)

LAS (reader LAS_1) [off]
    -> PointCloudPropertyExtractor
PointCloudPropertyExtractor [off]
    POINT_COMPONENTS_EXISTANCE_DISPLAY = "Intensity" "Color" "Classification" "Return" "Number Of Returns" "Angle" "Flight Line" "Scan Direction" "Point Source Id" "POSIX Time" "GPS Time" "GPS Week" "Flight Line Edge" "User Data"
    CALCULATE_EXTENTS_DISPLAY = No
    -> PointCloudPropertyExtractor_OUTPUT
PointCloudPropertyExtractor_OUTPUT: Inspector [off]
1164212 (reader CSV_1) [off]
    attributes: col0 number(10,3), col1 number(10,3), col2 number(7,3), col3 number(4,0), col4 number(4,0), col5 number(4,0)
    -> demo (writer JSON_1)
demo (writer JSON_1) [off]
    attributes: x float, y float, z float, r float, g float, b float
